module testme-1 {
    description "testing loading yang files";
 
    container z {
        description "Z";

        leaf q {
            type int32;
        }
    }

    leaf x { 
        type string;
    }

    leaf y {
        type enumeration {
            enum one;
            enum two;
            enum four {
                value 4;
            }
        }
    }
}
