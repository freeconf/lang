module echo {
    grouping x {
        leaf f {
            type int32;
        }
        container g {
            leaf s {
                type string;
            }
        }
    }

    rpc echo {

        // "input is returned in output";

        input {
            uses x;
        }
        output {
            uses x;
        }
    }

    rpc send {
        input {
            uses x;
        }
    }

    notification recv {
        // message is sent then send is called and it just sends payload in message
        uses x;
    }
}
