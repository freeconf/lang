module testme {
    description "testing loading yang files";
    prefix "t";

    extension x {
        description "x desc here";
        argument "arg0";
    }

    leaf x { 
        type string;
        t:x "arg here";
    }

    container z {
        description "Z";

        leaf-list q {
            type int32;
        }
    }
}
