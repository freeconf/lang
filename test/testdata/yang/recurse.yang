module recurse {

    grouping x {
        container z {
            leaf a {
                type string;
            }
            uses x;
        }
    }
    uses x;

    grouping p {
        container q {
            leaf f {
                type string;
            }
        }
    }

    container zz {
        uses p;
        container zzz {
            uses p;
        }
    }
}
