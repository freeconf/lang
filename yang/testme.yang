module testme {
    description "testing loading yang files";

    leaf x { 
        type string;
    }

    container z {
        description "Z";

        leaf-list q {
            type int32;
        }
    }
}
