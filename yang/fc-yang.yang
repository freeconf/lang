module fc-yang {
    namespace "freeconf.org/fc-yang";
    prefix "schema";
    description
      "YANG definition of YANG";
    revision 0000-00-00;

    /* 
     *   NOTES:

     *   !! contains CIRCULAR references however there is no other way around
     *   this.  According to RFC7950 this is not allowed.
     */
    container module {
        uses def-header;

        leaf namespace {
            type string;
        }
        leaf prefix {
            type string;
        }
        leaf contact {
            type string;
        }
        leaf organization {
            type string;
        }
        leaf version {
            type string;
        }
        grouping revisionDef {
            leaf ident {
                type string;
            }
            leaf description {
                type string;
            }
            leaf reference {
                type string;
            }
        }
        container revision {
            uses revisionDef;
        }
        list revisions {
            key ident;
            uses revisionDef;
        }
        uses actions-notifys;
        uses data-defs;
        list identity {
            key "ident";
            uses def-header;
            leaf-list baseIds {
                type string;
            }
            leaf-list derivedIds {
                type string;
            }
        }
        list feature {
            key "ident";
            uses def-header;
        }

        list extensionDef {
            key "ident";

            uses def-header;

            list argument {

                uses def-header;

                leaf yinElement {
                    type boolean;
                }
            }
        }
    }

    grouping extension {
        leaf prefix {
            type string;
        }

        leaf ident {
            type string;
        }

        leaf keyword {
            description
              "If extension is on a keyword and not on main 
               YANG contruct. For example an extension on 'description' 
               would have keyword 'description' here.";
            type string;
        }

        leaf-list arguments {
            type string;
        }
    }

    grouping def-header {
        leaf ident {
            type string;
        }
        leaf description {
            type string;
        }
        leaf reference {
            type string;
        }
        leaf status {
            type enumeration {
                enum current;
                enum deprecated;
                enum obsolete;
            }
        }
        list extension {
            uses extension;
        }
    }

    grouping when {
        leaf when {
            type string;
        }
    }

    grouping error-message {
        leaf description {
            type string;
        }
        leaf reference {
            type string;
        }
        leaf errorMessage {
            type string;
        }
        leaf errorAppTag {
            type string;
        }
    }

    grouping def-meta {
        leaf description {
            type string;
        }
        leaf reference {
            type string;
        }
    }

    grouping musts {
        list must {
            leaf expression {
                type string;
            }
            uses error-message;
        }
    }

    grouping type {
        container type {
            uses type-contents;
        }
    }

    grouping type-contents {
        leaf ident {
            type string;
        }
        list enumeration {
            key "label";
            leaf label {
                type string;
            }
            leaf id {
                type int32;
            }
            uses def-meta;
        }
        list bit {
            key "label";
            leaf label {
                type string;
            }
            leaf position {
                type int32;
            }
            uses def-meta;
        }
        leaf path {
            type string;
        }
        leaf requireInstance {
            type boolean;
        }
        leaf base {
            type leafref {
                path "/module/identity/ident";
            }
        }
        list union {
            uses type-contents;
        }
        list length {
            leaf length {
                type string;
            }
            uses error-message;
        }
        list range {
            leaf range {
                type string;
            }
            uses error-message;
        }
        leaf fractionDigits {
            type int32;
        }
        list pattern {
            leaf pattern {
                type string;
            }
            uses error-message;
            leaf invert {
                description "invert the regex pattern so it fails if it does match.";
                type boolean;
            }
        }
        leaf format {
            description
              "type control format";
            config false;
            type enumeration {
                enum binary {
                    value 1;
                }
                enum bits;
                enum boolean;
                enum decimal64;
                enum empty;
                enum enum;
                enum identityRef;
                enum instanceRef;
                enum int8;
                enum int16;
                enum int32;
                enum int64;
                enum leafRef;
                enum string;
                enum uint8;
                enum uint16;
                enum uint32;
                enum uint64;
                enum union;
                enum any;
                enum binaryList {
                    value 1025;
                }
                enum bitsList;
                enum booleanList;
                enum decimal64List;
                enum emptyList;
                enum enumList;
                enum identityRefList;
                enum instanceRefList;
                enum int8List;
                enum int16List;
                enum int32List;
                enum int64List;
                enum leafRefList;
                enum stringList;
                enum uint8List;
                enum uint16List;
                enum uint32List;
                enum uint64List;
                enum unionList;
                enum anyList;
            }
        }
    }

    grouping has-details {
        leaf config {
            type boolean;
        }
        leaf mandatory {
            type boolean;
        }
    }

    grouping has-list-details {
        leaf orderedBy {
            type enumeration {
                enum system;
                enum user;
            }
        }
        leaf minElements {
            type int32;
        }
        leaf maxElements {
            type int32;
        }
        leaf unbounded {
            type boolean;
        }
    }

    grouping actions-notifys {
        list action {
            key "ident";
            uses def-header;
            container input {
                uses data-defs;
                uses musts;
            }
            container output {
                uses data-defs;
                uses musts;
            }
        }
        list notify {
            key "ident";
            uses def-header;
            uses data-defs;
        }
    }

    grouping has-default {
        leaf default {
            type string;
        }
    }

    grouping units {
        leaf units {
            type string;
        }
    }

    grouping data-defs {
        list dataDef {
            key "ident";
            uses def-header;
            uses when;
            choice body-stmt {
                case container {
                    container container {
                        uses has-details;
                        uses musts;
                        uses data-defs;
                        uses actions-notifys;
                    }
                }
                case list {
                    container list {
                        leaf-list key {
                            type string;
                        }
                        uses has-details;
                        uses musts;
                        uses has-list-details;
                        uses data-defs;
                        uses actions-notifys;
                    }
                }
                case leaf {
                    container leaf {
                        uses has-default;
                        uses has-details;
                        uses units;
                        uses musts;
                        uses type;
                    }
                }
                case anyxml {
                    container anyxml {
                        uses has-details;
                        uses musts;
                        uses type;
                    }
                }
                case leaf-list {
                    container leaf-list {
                        uses has-default;
                        uses has-details;
                        uses has-list-details;
                        uses units;
                        uses musts;
                        uses type;
                    }
                }
                case choice {
                    container choice {
                        // conflicts w/RFC, but only because of short-hand representation
                        // when there's an implied "case", schema will represent full representation
                        uses data-defs;
                    }
                }
                case case {
                    container case {
                        uses musts;
                        uses data-defs;
                        uses actions-notifys;
                    }
                }
            }
        }
    }
}
